(defun C:Tes ()
  (if *HGPSPOLY
    (progn
;;;=== Begin of Global Variable ===============================================================

      (princ);;hapus jika ingin memasukam proses

        

;;;********************************************************************************************
;;;=== Action End ============================================================================
;;;********************************************************************************************
      (prompt
	(strcat
	  "\ntool set : polygpselev"
	  "\nEditor & Programmer : Pahor. M | tempuyax@yahoo.com.sg | Nunukan - April 2019"
	) ;_ end of strcat
      ) ;_ end of prompt

;;;=== End of Global Variable ===============================================================
    ) ;_ end of progn
    (prompt "\n***As GPS Belum di Dibuat***")
  ) ;_ end of if
  (princ)
) ;_ end of defun

;;;********************************************************************************************
;;;=== END OF =================================================================================
;;;********************************************************************************************
